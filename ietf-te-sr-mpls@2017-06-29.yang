module ietf-te-sr-mpls {

  namespace "urn:ietf:params:xml:ns:yang:ietf-te-sr-mpls";

  /* Replace with IANA when assigned */
  prefix "te-sr-mpls";

  /* Import TE generic types */
  import ietf-te {
    prefix te;
  }

  /* Import TE generic types */
  import ietf-te-types {
    prefix te-types;
  }

  organization
    "IETF Traffic Engineering Architecture and Signaling (TEAS)
     Working Group";

  contact
    "WG Web:   <http://tools.ietf.org/wg/teas/>
     WG List:  <mailto:teas@ietf.org>

     WG Chair: Lou Berger
               <mailto:lberger@labn.net>

     WG Chair: Vishnu Pavan Beeram
               <mailto:vbeeram@juniper.net>

     Editor:   Tarek Saad
               <mailto:tsaad@cisco.com>

     Editor:   Rakesh Gandhi
               <mailto:rgandhi@cisco.com>

     Editor:   Vishnu Pavan Beeram
               <mailto:vbeeram@juniper.net>

     Editor:   Himanshu Shah
               <mailto:hshah@ciena.com>

     Editor:   Xufeng Liu
               <mailto:xufeng.liu@ericsson.com>

     Editor:   Xia Chen
               <mailto:jescia.chenxia@huawei.com>

     Editor:   Raqib Jones
               <mailto:raqib@Brocade.com>

     Editor:   Bin Wen
               <mailto:Bin_Wen@cable.comcast.com>";

  description
    "YANG data module for MPLS TE configurations,
    state, RPC and notifications.";

  revision "2017-06-29" {
    description "Latest update to MPLS TE YANG module.";
    reference "TBD";
  }

  identity sr-protection-type {
    description
       "The Adj-SID base protection types";
  }

  identity sr-protection-type-protected {
    base sr-protection-type;
    description
       "The Adj-SID is eligible if protected";
  }

  identity sr-protection-type-unprotected {
    base sr-protection-type;
    description
       "The Adj-SID is eligible if unprotected";
  }

  identity sr-protection-type-any {
    base sr-protection-type;
    description
       "The Adj-SID is eligible if protected or unprotected";
  }

  typedef te-sid-selection-mode {
    type enumeration {
      enum ADJ_SID_ONLY {
        description
          "The SR-TE tunnel should only use adjacency SIDs
          to build the SID stack to be pushed for the LSP";
      }
      enum MIXED_MODE {
        description
          "The SR-TE tunnel can use a mix of adjacency
          and prefix SIDs to build the SID stack to be pushed
          to the LSP";
      }
    }
    description "SID selection mode type";
  }

  /* MPLS SR-TE tunnel properties*/
  grouping tunnel-sr-mpls-properties_config {
    description "MPLS TE SR tunnel properties";
    leaf path-signaling-type {
      type identityref {
        base te-types:path-signaling-type;
      }
      description "TE tunnel path signaling type";
    }
  }

  grouping te-sr-named-path-constraints_config {
    description
      "Configuration parameters relating to SR-TE LSPs";

    leaf sid-selection-mode {
      type te-sid-selection-mode;
      default MIXED_MODE;
      description
        "The restrictions placed on the SIDs to be selected by the
        calculation method for the explicit path when it is
        instantiated for a SR-TE LSP";
    }

    leaf sid-protection {
      type identityref {
        base sr-protection-type;
      }
      default sr-protection-type-any;
      description
        "When set to protected only SIDs that are
        protected are to be selected by the calculating method
        when the explicit path is instantiated by a SR-TE LSP.";
    }
  }

  grouping te-sr-named-path-constraints {
    description "Named TE SR path constraints grouping";
    container config {
      description
        "Configuration parameters related to TE SR named
         path constraints";
      uses te-sr-named-path-constraints_config;
    }
    container state {
      config false;
      description
        "State parameters related to TE SR named
         path constraints";
      uses te-sr-named-path-constraints_config;
    }
  }
  /*** End of MPLS SR-TE tunnel configuration/state */


  /**
   * MPLS TE augmentations
   */

  /* MPLS TE global augmentations */
  augment "/te:te/te:globals/te:named-path-constraints" +
          "/te:named-path-constraint" {
    description
        "Augmentations for MPLS SR-TE config named constraints";
    uses te-sr-named-path-constraints;
  }

  /* MPLS TE tunnel augmentations */

  /* MPLS TE LSPs augmentations */
}
